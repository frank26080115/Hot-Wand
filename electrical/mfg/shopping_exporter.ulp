/*
 * Shopping BOM exporter for EAGLE 7.x.
 *
 * Inspired by jlcpcb_smta_exporter.ulp:
 * Copyright 2019 OXullo Intersecans <x@brainrapers.org>
 *
 * Permission is hereby granted, free of charge, to any person obtaining a copy
 * of this software and associated documentation files (the "Software"), to
 * deal in the Software without restriction, including without limitation the
 * rights to use, copy, modify, merge, publish, distribute, sublicense, and/or
 * sell copies of the Software, and to permit persons to whom the Software is
 * furnished to do so, subject to the following conditions:
 *
 * The above copyright notice and this permission notice shall be included in
 * all copies or substantial portions of the Software.
 *
 * THE SOFTWARE IS PROVIDED "AS IS", WITHOUT WARRANTY OF ANY KIND, EXPRESS OR
 * IMPLIED, INCLUDING BUT NOT LIMITED TO THE WARRANTIES OF MERCHANTABILITY,
 * FITNESS FOR A PARTICULAR PURPOSE AND NONINFRINGEMENT. IN NO EVENT SHALL THE
 * AUTHORS OR COPYRIGHT HOLDERS BE LIABLE FOR ANY CLAIM, DAMAGES OR OTHER
 * LIABILITY, WHETHER IN AN ACTION OF CONTRACT, TORT OR OTHERWISE, ARISING
 * FROM, OUT OF OR IN CONNECTION WITH THE SOFTWARE OR THE USE OR OTHER DEALINGS
 * IN THE SOFTWARE.
 */

#usage "<b>Shopping BOM CSV exporter</b>\n"
       "<p>Exports a single BOM containing assembly classification, "
       "manufacturer part numbers, and LCSC part numbers."
       "<p>Run the ULP from the board editor."
       "<p>An optional first argument selects the output directory."


UL_ELEMENT selected_elements[];


string strip(string s)
{
    int i, n;
    string t;

    while (s && isspace(s[0])) {
        s = strsub(s, 1);
    }

    while (s && isspace(s[strlen(s) - 1])) {
        s = strsub(s, 0, strlen(s) - 1);
    }

    for (i = 0; i < strlen(s); i++) {
        if (!isspace(s[i])) {
            t[n++] = s[i];
        } else if (!((strlen(s) > i + 1) && isspace(s[i + 1]))) {
            t[n++] = s[i];
        }
    }

    return t;
}


string csv_field(string s)
{
    int i, n = 1;
    string t = "\"";

    for (i = 0; i < strlen(s); i++) {
        // EAGLE exposes UTF-8 bytes as signed characters. Drop all non-ASCII
        // bytes to keep the output accepted by simple purchasing tools.
        if (s[i] < 0 || s[i] >= 128) {
            continue;
        }

        if (s[i] == '\r' || s[i] == '\n' || s[i] == '\t') {
            t[n++] = ' ';
        } else if (s[i] == '"') {
            // CSV escapes a quote by doubling it.
            t[n++] = '"';
            t[n++] = '"';
        } else {
            t[n++] = s[i];
        }
    }

    t[n++] = '"';
    return t;
}


string get_attribute(UL_ELEMENT E, string attribute_name)
{
    E.attributes(A) {
        if (A.name == attribute_name) {
            return A.value;
        }
    }
    return "";
}


string get_lcsc_part(UL_ELEMENT E)
{
    E.attributes(A) {
        if (A.name == "LCSC_PART" || A.name == "LCSC" ||
                A.name == "JLCPARTNUM") {
            return A.value;
        }
    }
    return "";
}


int is_dnp(UL_ELEMENT E)
{
    if (!E.populate) {
        return 1;
    }

    if (strupr(strip(E.value)) == "DNP") {
        return 1;
    }

    E.attributes(A) {
        if (A.name == "DNP" || A.name == "JLC-DNP") {
            return 1;
        }
    }

    // Keep solder jumpers in the shopping BOM, but mark them as DNP.
    if (strstr(E.name, "SJ") == 0) {
        return 1;
    }

    return 0;
}


string get_assembly(UL_ELEMENT E)
{
    int has_smd = 0;
    int has_th = 0;

    E.package.contacts(C) {
        if (C.smd) {
            has_smd = 1;
        }
        if (C.pad) {
            has_th = 1;
        }
    }

    string mount_type;
    if (has_smd && has_th) {
        mount_type = "MIX";
    } else if (has_smd) {
        mount_type = "SMD";
    } else if (has_th) {
        mount_type = "TH";
    } else {
        // Mechanical/cosmetic packages can have holes or artwork but no pads.
        mount_type = "MECH";
    }

    string assembly = E.mirror ? "BOTTOM-" : "TOP-";
    assembly += mount_type;

    if (is_dnp(E)) {
        assembly = "DNP-" + assembly;
    }

    return assembly;
}


string append_designator(string designators, string name)
{
    if (designators != "") {
        designators += " ";
    }
    designators += name;
    return designators;
}


if (board) board(B) {
    int interactive = argc < 2;
    string output_dir;

    if (interactive) {
        output_dir = dlgDirectory("Export shopping BOM to", filedir(B.name));
    } else {
        output_dir = argv[1];
    }

    if (output_dir == "") {
        exit(0);
    }

    int element_count = 0;
    B.elements(E) {
        selected_elements[element_count++] = E;
    }

    string board_filename = filename(B.name);
    string board_basename = strsub(board_filename, 0, strlen(board_filename) - 4);
    string bom_filename = output_dir + "/" + board_basename + "-bom.csv";

    output(bom_filename) {
        int i;
        int indexes[];
        numeric string values[];
        numeric string footprints[];
        numeric string assemblies[];
        numeric string manufacturer_parts[];
        numeric string lcsc_parts[];

        for (i = 0; i < element_count; ++i) {
            indexes[i] = i;
            values[i] = selected_elements[i].value;
            footprints[i] = selected_elements[i].package.name;
            assemblies[i] = get_assembly(selected_elements[i]);
            manufacturer_parts[i] = get_attribute(selected_elements[i], "PARTNUM");
            lcsc_parts[i] = get_lcsc_part(selected_elements[i]);
        }

        sort(element_count, indexes, values, footprints,
             assemblies, manufacturer_parts, lcsc_parts);

        printf("Comment,Designator,Footprint,Asm,Mfg Part #,LCSC Part #\n");

        string designators;
        for (i = 0; i < element_count; ++i) {
            int element_index = indexes[i];
            UL_ELEMENT E = selected_elements[element_index];
            string assembly = assemblies[element_index];
            string mfg_part = manufacturer_parts[element_index];
            string lcsc_part = lcsc_parts[element_index];
            int aggregate_with_next = 0;

            if (i < element_count - 1) {
                int next_index = indexes[i + 1];
                aggregate_with_next = (
                    E.value == selected_elements[next_index].value &&
                    E.package.name == selected_elements[next_index].package.name &&
                    assembly == assemblies[next_index] &&
                    mfg_part == manufacturer_parts[next_index] &&
                    lcsc_part == lcsc_parts[next_index]
                );
            }

            if (strip(E.value) == "") {
                printf("%s,%s,%s,%s,%s,%s\n",
                    csv_field(""),
                    csv_field(E.name),
                    csv_field(E.package.name),
                    csv_field(assembly),
                    csv_field(mfg_part),
                    csv_field(lcsc_part));
                designators = "";
            } else if (aggregate_with_next) {
                designators = append_designator(designators, E.name);
            } else {
                designators = append_designator(designators, E.name);
                printf("%s,%s,%s,%s,%s,%s\n",
                    csv_field(E.value),
                    csv_field(designators),
                    csv_field(E.package.name),
                    csv_field(assembly),
                    csv_field(mfg_part),
                    csv_field(lcsc_part));
                designators = "";
            }
        }
    }

    if (interactive) {
        dlgMessageBox("Shopping BOM exported to: " + bom_filename, "OK");
    }

} else {
    dlgMessageBox("Run this ULP from a Board", "OK");
    exit(1);
}
